package SwTests

import Generic
import SwRequirements

section "SW Tests" {

    Generic.Info sw_test_info_about_sw_test {
        description = "This file contains the software test cases for the lobster-doxygen tool."
    }

    section "Functionality" {
        SwTestCase tc_output_file_format {
            description = "This test case verifies that the tool parses the 'index.xml' Doxygen XML output file as the root file, and that the output file is in the LOBSTER common interchange format."
            verifies = [SwRequirements.sw_req_output_file_format]
        }

        SwTestCase tc_function_level {
            description = "This test case checks whether requirements and justifications can be specified in function/prototype level."
            verifies = [SwRequirements.sw_req_function_level]
        }

        SwTestCase tc_type_level {
            description = "This test case checks whether requirements and justifications can be specified in struct/union/class level."
            verifies = [SwRequirements.sw_req_type_level]
        }

        SwTestCase tc_namespace_level {
            description = "This test case checks whether requirements and justifications can be specified in namespace level."
            verifies = [SwRequirements.sw_req_namespace_level]
        }

        SwTestCase tc_method_level {
            description = "This test case checks whether requirements and justifications can be specified in methods level independent of visibility."
            verifies = [SwRequirements.sw_req_method_level]
        }

        SwTestCase tc_interface_level {
            description = "This test case checks whether requirements and justifications can be specified in interface level."
            verifies = [SwRequirements.sw_req_interface_level]
        }

        SwTestCase tc_no_group {
            description = "This test case checks whether requirements and justifications work outside of doxygen groups."
            verifies = [SwRequirements.sw_req_no_group]
        }

        SwTestCase tc_group {
            description = "This test case checks whether requirements and justifications work in doxygen groups."
            verifies = [SwRequirements.sw_req_group]
        }

        SwTestCase tc_rule_file {
            description = "This test case checks that the program abort with an error if requirements or justifications are specified on file level."
            verifies = [SwRequirements.sw_req_file_level, SwRequirements.sw_req_rule_file]
        }

        SwTestCase tc_rule_class {
            description = "This test case checks that the program abort with an error if requirements or justifications on class/interface/namespace level and at least on of its methods."
            verifies = [SwRequirements.sw_req_rule_class]
        }

        SwTestCase tc_unspecified {
            description = "This test case checks whether the program works with all supported levels without requirements or a justification."
            verifies = [SwRequirements.sw_req_unspecified]
        }

        SwTestCase tc_no_trace {
            description = "This test case checks whether the program outputs a warning and creates a 'empty' lobster common interchange file."
            verifies = [SwRequirements.sw_req_no_trace]
        }

        SwTestCase tc_valid_id {
            description = "This test case checks whether the program correctly ignores parsed doxygen output containing code comments after the requirement id."
            verifies = [SwRequirements.sw_req_valid_id]
        }

        SwTestCase tc_invalid_input {
            description = "This test case checks whether the program reports an error on invalid requirements identifier input."
            verifies = [SwRequirements.sw_req_invalid_input]
        }
    }

    section "General" {

        SwTestCase tc_cli {
            description = "This test case checks whether the tool supports the command line arguments."
            verifies = [SwRequirements.sw_req_cli]
        }

        SwTestCase tc_stdout {
            description = "This test case checks whether the normal program output is printed to the stdout stream."
            verifies = [SwRequirements.sw_req_stdout_output]
        }

        SwTestCase tc_stderr {
            description = "This test case checks whether the program output is printed to the stderr stream if the program throws an error."
            verifies = [SwRequirements.sw_req_stderr_output]
        }
    }

    section "User Interface" {

        SwTestCase tc_help {
            description = "This test case checks whether the help information is shown with '--help' argument."
            verifies = [SwRequirements.sw_req_cli_help]
        }

        SwTestCase tc_output {
            description = "This test case checks that the software correctly sets the output file name when provided via the -o or --output command-line argument."
            verifies = [SwRequirements.sw_req_cli_output]
        }

        SwTestCase tc_version {
            description = "This test case checks whether the version information is shown with '--version' argument."
            verifies = [SwRequirements.sw_req_cli_version]
        }

        SwTestCase tc_verbose {
            description = "This test case check whether in verbose mode more information is printed out."
            verifies = [SwRequirements.sw_req_cli_verbose]
        }

        SwTestCase tc_doxygen_xml_folder {
            description = "This test case checks whether the doxygen_xml_folder is a positional argument."
            verifies = [SwRequirements.sw_req_cli_doxygen_xml_folder]
        }
    }
}
